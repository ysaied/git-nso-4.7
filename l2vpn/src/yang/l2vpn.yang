module l2vpn {
  namespace "http://yang.ysaied.com/nso/l2vpn";
  prefix l2vpn;

  import ietf-inet-types {
    prefix inet;
  }
  import tailf-ncs {
    prefix ncs;
  }
  import tailf-common {
    prefix tailf;
  }

  augment /ncs:services {
    list l2vpn {
      key name;
      unique pw-id;
      uses ncs:service-data;
      ncs:servicepoint "l2vpn";
      leaf name {
	description "l2vpn instance name";
	type string;
      }
      leaf pw-id {
	description "l2vpn pseudowire id";
	mandatory true;
	type uint16;
      }
      list edge-node {
	key name;
	leaf name {
	  description "l2vpn service edge router";
	  mandatory true;
	  type leafref {
	    path  "/ncs:devices/ncs:device/ncs:name";
	  }
	}
	leaf loopback-ip {
	  description "edge router loopback for l2vpn service termination";
	  mandatory true;
	  type inet:ipv4-address;
	}
	leaf attachemnt-circuit {
	  description "edge router service side interface";
	  mandatory true;
	  type string;
	}
      }
    }
  }
}
